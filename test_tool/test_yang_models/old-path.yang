submodule old-path {
  yang-version 1.1;
  belongs-to vpn-services { prefix main; }
  namespace "urn:test:old-path";
  prefix op;

  revision 2024-01-01 {
    description "Old version — XPath comparison test cases (pyang-validated)";
  }

  // ═══════════════════════════════════════════════════════════════════════════
  // REFERENCE DATA NODES at module root
  // XPath from leaf inside any sibling container:
  //   ..  = parent container
  //   ../.. = module root
  //   ../../config = config container ✓ (pyang-validated)
  // ═══════════════════════════════════════════════════════════════════════════

  container config {
    leaf name { type string; }
    leaf index { type uint32; }
    leaf admin-state {
      type enumeration {
        enum UP   { value 1; }
        enum DOWN { value 2; }
      }
    }
    leaf protocol-type {
      type enumeration {
        enum BGP   { value 1; }
        enum OSPF  { value 2; }
        enum ISIS  { value 3; }
      }
    }
  }

  container state {
    leaf name { type string; }
  }

  // ═══════════════════════════════════════════════════════════════════════════
  // LEAFREF TESTS
  // From leaf inside leafref-tests:
  //   ../../config/name = config/name ✓ (pyang-validated)
  //   ../../state/name  = state/name  ✓
  // ═══════════════════════════════════════════════════════════════════════════

  container leafref-tests {

    // Case A: path unchanged — EQUIVALENT (BC)
    leaf case-a-unchanged {
      type leafref { path "../../config/name"; }
      description "Case A: path unchanged — EQUIVALENT (BC)";
    }

    // Case A: path rewritten to absolute form — same target (BC)
    leaf case-a-rewritten {
      type leafref { path "../../config/name"; }
      description "Case A: path rewritten to absolute — EQUIVALENT (BC)";
    }

    // Case B: path changes to different node (name → index) — NBC
    leaf case-b-different-target {
      type leafref { path "../../config/name"; }
      description "Case B: old=config/name, new=config/index — INCOMPARABLE (NBC)";
    }

    // Case B: path changes to different container (config → state) — NBC
    leaf case-b-different-container {
      type leafref { path "../../config/name"; }
      description "Case B: old=config/name, new=state/name — INCOMPARABLE (NBC)";
    }

    // Case C: old path was broken (nonexistent-container), new is valid — BC
    leaf case-c-fix-broken-path {
      type leafref { path "../../nonexistent-container/name"; }
      description "Case C: old invalid, new valid — RELAXED (BC)";
    }

    // Case D: old path was valid, new path is broken — NBC
    leaf case-d-break-valid-path {
      type leafref { path "../../config/name"; }
      description "Case D: old valid, new invalid — NARROWED (NBC)";
    }

    // Case E: both paths invalid — NBC
    leaf case-e-both-invalid {
      type leafref { path "../../nonexistent-a/name"; }
      description "Case E: both invalid — INCOMPARABLE (NBC)";
    }

    // Leafref → string (type change away from leafref) — BC
    leaf case-leafref-to-string {
      type leafref { path "../../config/name"; }
      description "leafref → string: BC";
    }

    // string → leafref (type change to leafref) — NBC
    leaf case-string-to-leafref {
      type string;
      description "string → leafref: NBC";
    }
  }

  // ═══════════════════════════════════════════════════════════════════════════
  // CONDITION TESTS — each condition text is UNIQUE
  // From leaf inside condition-tests:
  //   ../../config/admin-state = config/admin-state ✓ (pyang-validated)
  // ═══════════════════════════════════════════════════════════════════════════

  container condition-tests {

    // LHS unchanged — EQUIVALENT (BC)
    leaf cond-lhs-unchanged {
      when "../../config/index = 1";
      type string;
      description "LHS path unchanged — EQUIVALENT (BC)";
    }

    // LHS path changes to DIFFERENT node:
    //   Old: ../../config/admin-state = 'UP'  (valid)
    //   New: ../../config/protocol-type = 'BGP' (valid, different node)
    //   → INCOMPARABLE (NBC)
    leaf cond-lhs-different-node {
      when "../../config/admin-state = 'UP'";
      type string;
      description "LHS changes to different node — INCOMPARABLE (NBC)";
    }

    // LHS path was invalid (nonexistent), new is valid — RELAXED (BC)
    leaf cond-lhs-fix-broken {
      when "../../nonexistent/admin-state = 'UP'";
      type string;
      description "LHS was invalid, now valid — RELAXED (BC)";
    }

    // LHS path was valid, new is invalid — NARROWED (NBC)
    leaf cond-lhs-break-valid {
      when "../../config/admin-state = 'DOWN'";
      type string;
      description "LHS was valid, now invalid — NARROWED (NBC)";
    }

    // RHS enum unchanged — EQUIVALENT (BC)
    leaf cond-rhs-enum-unchanged {
      when "../../config/protocol-type = 'BGP'";
      type string;
      description "RHS enum unchanged — EQUIVALENT (BC)";
    }

    // RHS enum changes to different valid value — INCOMPARABLE (NBC)
    leaf cond-rhs-enum-change {
      when "../../config/protocol-type = 'OSPF'";
      type string;
      description "RHS enum changes OSPF→ISIS — INCOMPARABLE (NBC)";
    }

    // RHS enum was invalid (INVALID_ENUM), new is valid — RELAXED (BC)
    leaf cond-rhs-enum-fix {
      when "../../config/admin-state = 'INVALID_ENUM'";
      type string;
      description "RHS enum was invalid, now valid — RELAXED (BC)";
    }

    // RHS enum was valid, new is invalid — NARROWED (NBC)
    leaf cond-rhs-enum-break {
      when "../../config/protocol-type = 'ISIS'";
      type string;
      description "RHS enum was valid, now invalid — NARROWED (NBC)";
    }

    // RHS identity unchanged — EQUIVALENT (BC)
    leaf cond-rhs-identity-unchanged {
      when "../../config/index = 10";
      type string;
      description "RHS identity unchanged — EQUIVALENT (BC)";
    }

    // RHS identity changes — INCOMPARABLE (NBC)
    leaf cond-rhs-identity-change {
      when "../../config/admin-state = 'UP' and ../../config/index = 5";
      type string;
      description "RHS identity changes — INCOMPARABLE (NBC)";
    }

    // RHS unquoted node-location path — EQUIVALENT (BC)
    leaf cond-rhs-node-unchanged {
      when "../../config/admin-state";
      type string;
      description "RHS unquoted node-location unchanged — EQUIVALENT (BC)";
    }

    // OR condition: both alternatives equivalent — EQUIVALENT (BC)
    leaf cond-or-equivalent {
      when "../../config/admin-state = 'UP' or ../../config/admin-state = 'DOWN'";
      type string;
      description "OR condition — both alternatives equivalent (BC)";
    }

    // OR condition: new alternative added — RELAXED (BC)
    leaf cond-or-relaxed {
      when "../../config/index > 0";
      type string;
      description "OR condition — new alternative added (RELAXED, BC)";
    }

    // OR condition: alternative removed — NARROWED (NBC)
    leaf cond-or-narrowed {
      when "../../config/index > 0 or ../../config/index < 100";
      type string;
      description "OR condition — alternative removed (NARROWED, NBC)";
    }

    // AND condition: requirement added — NARROWED (NBC)
    leaf cond-and-narrowed {
      when "../../config/index > 0 and ../../config/index < 100";
      type string;
      description "AND condition — requirement added (NARROWED, NBC)";
    }

    // AND condition: requirement removed — RELAXED (BC)
    leaf cond-and-relaxed {
      when "../../config/index > 0 and ../../config/index < 50";
      type string;
      description "AND condition — requirement removed (RELAXED, BC)";
    }

    // must unchanged — EQUIVALENT (BC)
    leaf cond-must-unchanged {
      type string;
      must "../../config/index = 42" {
        error-message "Index must be 42";
      }
      description "must condition unchanged — EQUIVALENT (BC)";
    }

    // must was broken, now valid — RELAXED (BC)
    leaf cond-must-fix {
      type string;
      must "../../nonexistent2/admin-state = 'UP'" {
        error-message "Was broken";
      }
      description "must condition was broken, now valid — RELAXED (BC)";
    }

    // must was valid, now broken — NARROWED (NBC)
    leaf cond-must-break {
      type string;
      must "../../config/index = 99" {
        error-message "Will be broken";
      }
      description "must condition was valid, now broken — NARROWED (NBC)";
    }
  }

  // ═══════════════════════════════════════════════════════════════════════════
  // GROUPING / USES TESTS
  // When a grouping is instantiated via uses, the when/must conditions are
  // evaluated from the instantiation point.
  // From leaf inside uses-tests (via grouping):
  //   ../../config/admin-state = config/admin-state ✓
  // ═══════════════════════════════════════════════════════════════════════════

  grouping condition-grouping {
    description "Grouping with when conditions — evaluated at instantiation point";

    // Grouping case A: condition unchanged — EQUIVALENT (BC)
    leaf grp-cond-unchanged {
      when "../../config/admin-state = 'UP'";
      type string;
      description "Grouping condition unchanged — EQUIVALENT (BC)";
    }

    // Grouping case C: old condition broken, new valid — RELAXED (BC)
    leaf grp-cond-fix {
      when "../../nonexistent/admin-state = 'UP'";
      type string;
      description "Grouping condition was broken, now valid — RELAXED (BC)";
    }
  }

  // ── uses-when-tests: when condition on the uses statement itself ──────────────
  // Real-world pattern (from openconfig-if-aggregate.yang):
  //   uses my-grouping {
  //     when "../config/admin-state = 'UP'" { ... }
  //   }
  // The when on uses is evaluated from the PARENT CONTAINER context:
  //   From uses-when-tests container: ../config = config (sibling) ✓
  //   From uses-when-tests-or container: ../config = config (sibling) ✓

  grouping uses-when-grouping {
    description "Grouping instantiated with when conditions on the uses statement";
    leaf uses-when-leaf-a { type string; description "Leaf A in grouping"; }
    leaf uses-when-leaf-b { type string; description "Leaf B in grouping"; }
    leaf uses-when-leaf-d { type string; description "Leaf D in grouping"; }

        // Grouping case D: old condition valid, new broken — NARROWED (NBC)
    leaf grp-cond-break {
      when "../../config/admin-state = 'DOWN'";
      type string;
      description "Grouping condition was valid, now broken — NARROWED (NBC)";
    }
  }

  // Case A: when condition unchanged — EQUIVALENT (BC)
  container uses-when-tests {
    description "uses with when — condition unchanged (EQUIVALENT, BC)";
    uses uses-when-grouping {
      when "../config/admin-state = 'UP'" {
        description "Active when admin-state is UP";
      }
    }
  }

  // Case C: old when was broken (nonexistent), new is valid — RELAXED (BC)
  container uses-when-tests-fix {
    description "uses with when — old broken (too many ../), new valid (RELAXED, BC)";
    uses uses-when-grouping {
      when "../../config/protocol-type = 'ISIS'" {
        description "Was broken — too many levels up from uses context";
      }
    }
  }

  // Case D: old when was valid, new is broken — NARROWED (NBC)
  container uses-when-tests-break {
    description "uses with when — old valid, new broken (NARROWED, NBC)";
    uses uses-when-grouping {
      when "../config/admin-state = 'DOWN'" {
        description "Active when admin-state is DOWN";
      }
    }
  }

  // OR condition on uses: new alternative added — RELAXED (BC)
  container uses-when-tests-or-relaxed {
    description "uses with OR when — new alternative added (RELAXED, BC)";
    uses uses-when-grouping {
      when "../config/protocol-type = 'BGP'" {
        description "Active when protocol-type is BGP";
      }
    }
  }

  // OR condition on uses: alternative removed — NARROWED (NBC)
  container uses-when-tests-or-narrowed {
    description "uses with OR when — alternative removed (NARROWED, NBC)";
    uses uses-when-grouping {
      when "../config/protocol-type = 'BGP' or ../config/protocol-type = 'OSPF'" {
        description "Active when protocol-type is BGP or OSPF";
      }
    }
  }

  // AND condition on uses: requirement added — NARROWED (NBC)
  container uses-when-tests-and-narrowed {
    description "uses with AND when — requirement added (NARROWED, NBC)";
    uses uses-when-grouping {
      when "../config/protocol-type = 'BGP'" {
        description "Active when protocol-type is BGP";
      }
    }
  }

  // Enum fix on uses: old RHS invalid, new valid — RELAXED (BC)
  container uses-when-tests-enum-fix {
    description "uses with when — RHS enum was invalid, now valid (RELAXED, BC)";
    uses uses-when-grouping {
      when "../config/admin-state = 'INVALID_USES'" {
        description "Was broken — invalid enum value";
      }
    }
  }

  // Enum break on uses: old RHS valid, new invalid — NARROWED (NBC)
  container uses-when-tests-enum-break {
    description "uses with when — RHS enum was valid, now invalid (NARROWED, NBC)";
    uses uses-when-grouping {
      when "../config/admin-state = 'UP'" {
        description "Active when admin-state is UP";
      }
    }
  }

  // ═══════════════════════════════════════════════════════════════════════════
  // AUGMENT PATH CASES
  // ═══════════════════════════════════════════════════════════════════════════

  container augment-target {
    leaf target-leaf { type string; }
  }

  augment "/op:augment-target" {
    description "Augment case A: path unchanged — EQUIVALENT (BC)";
    leaf augment-case-a { type string; }
  }

  augment "/op:augment-target" {
    description "Augment case B: path changes to different target — INCOMPARABLE (NBC)";
    leaf augment-case-b { type string; }
  }
}
