submodule demo-defval {
  yang-version 1.1;
  belongs-to vpn-services { prefix main; }

  import smiv2-defs { prefix smiv2; }

  revision "2026-01-01" {
    description "Initial defval example.";
  }

  leaf ifMtu {
    type int32;
    description "Interface MTU.";
    smiv2:defval "1500";
    smiv2:max-access "read-write";
  }
}
